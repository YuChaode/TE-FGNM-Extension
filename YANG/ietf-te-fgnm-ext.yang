module ietf-te-fgnm-ext {
  yang-version 1.1;
  namespace "urn:ietf:params:xml:ns:yang:ietf-te-fgnm-ext";
  prefix te-fgnm-ext;
  
  import ietf-te {
    prefix "te";
  }
  
  import ietf-yang-types {
    prefix "yang";
  }

  import ietf-te-types-fgnm-ext {
    prefix "te-types-fgnm-ext";
  }  
  
  import ietf-network {
    prefix "nw";
  }  
  
  import ietf-network-topology {
    prefix "nt";
  }

  import ietf-te-topology {
    prefix "tet";
  }  
  
  organization
    "IETF CCAMP Working Group";
  contact
    "WG Web: <http://tools.ietf.org/wg/ccamp/>
     WG List: <mailto:ccamp@ietf.org>

     Editor: Chaode Yu
             <mailto:yuchaode@huawei.com>
             Xing Zhao 
             <mailto:zhaoxing@caict.ac.cn>";

  description
    "This module provide some extensions to TE topology model, based
    on transport fine-grain network management requirement";

  revision 2024-03-04 {
    description
      "Revision 1.0";
    reference
      "draft-yu-ccamp-te-fgnm-yang-00";
  }

  augment "/te:te/te:tunnels/te:tunnel" {
    leaf alias {
      description 
        "alias of TE tunnel";
      type string;
    }
  
    uses time-state-grouping;
    
    container source-endpoints {
      list source-endpoint {
        uses endpoint-grouping;
      }
    }
    
    container destination-endpoints {
      list destination-endpoint {
        uses endpoint-grouping;
      }
    }
  }
  
  augment  "/te:te/te:tunnels/te:tunnel/te:restoration" {
    leaf restoration-lock {
      description
        "a lock to control whether the restoration can take effect or
        not, it is useful in the maintenance scenrios, such as in
        cutover";
      type boolean;
    }
    
    leaf restoration-reversion-lock {
      description
        "a lock to control whether the reversion of restoration can
        take effect or not.";
      type boolean;
    }
    
    leaf scheduled-reversion-time {
      description
        "a time when the reversion of restoration can take effect.";
      type yang:date-and-time;
    }
    
    leaf restoration-priority {
      description
        "when there are multiple services need to be restored, the 
        higher estoration priority services can occupied the idle 
        resource in priority, it is used to control the restoration 
        sequence.";
      type enumeration {
        enum high;
        enum medium;
        enum low;
      }
    }
    
    leaf restoration-layer {
      description
        "the layer of topolgy prefered to be operated when restoration
        is needed.";
      type enumeration {
        enum odu;
        enum wdm;
      }
    }
  }
  
  augment  "/te:te/te:tunnels/te:tunnel/te:primary-paths"
           + "/te:primary-path/te:explicit-route-objects-always"
           + "/te:route-object-include-exclude/te:type"    {
    description 
      "a TTP hop";
    case ttp-hop {
      uses te-types-fgnm-ext:explicit-ttp-hop;
    }
  }
  
  augment  "/te:te/te:tunnels/te:tunnel/te:secondary-paths"
           + "/te:secondary-path/te:explicit-route-objects-always"
           + "/te:route-object-include-exclude/te:type"    {
    description 
      "a TTP hop";
    case ttp-hop {
      uses te-types-fgnm-ext:explicit-ttp-hop;
    }
  }  
  
  augment  "/te:te/te:tunnels/te:tunnel/te:primary-paths"
           + "/te:primary-path/te:primary-reverse-path"
           + "/te:explicit-route-objects-always"
           + "/te:route-object-include-exclude/te:type"    {
    description 
      "a TTP hop";
    case ttp-hop {
      uses te-types-fgnm-ext:explicit-ttp-hop;
    }
  }
  
  augment  "/te:te/te:tunnels/te:tunnel/te:secondary-reverse-paths"
           + "/te:secondary-reverse-path"
           + "/te:explicit-route-objects-always"
           + "/te:route-object-include-exclude/te:type"    {
    description 
      "a TTP hop";
    case ttp-hop {
      uses te-types-fgnm-ext:explicit-ttp-hop;
    }
  }    
  
  grouping time-state-grouping {
    leaf create-time {
      config false;
      description
        "the time when the tunnel was created";
      type yang:date-and-time;
    }
    
    leaf active-time {
      config false;
      description
        "the lastest time when the tunnel was activated";
      type yang:date-and-time;
    }    
  }
  
  grouping endpoint-grouping {
    leaf node-id {
      type leafref {
        path "/nw:networks/nw:network/nw:node/nw:node-id";
      }
    }
    
    choice endpoint-tp {
      case ltp {
        leaf tp-id {
          type leafref {
            path "/nw:networks/nw:network/nw:node/nt:termination-point"
            + "/nt:tp-id";
          }
        }
      }
      
      case ttp {
        choice id-or-name {
          case id {
            leaf ttp-id {
              type leafref {
                path "/nw:networks/nw:network/nw:node/tet:te"
                + "/tet:tunnel-termination-point/tet:tunnel-tp-id";
              }
            }
          }
          
          case name {
            leaf ttp-name {
              type leafref {
                path "/nw:networks/nw:network/nw:node/tet:te"
                + "/tet:tunnel-termination-point/tet:name";
              }
            }
          }
        }
      }
    }
    
    leaf protection-role {
      description
        "role of this endpoint in multipoints scenario";
      type enumeration {
        enum work;
        enum protect;
      }
    }
  }
  
}
